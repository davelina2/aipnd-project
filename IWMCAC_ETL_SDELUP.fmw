FME workspace IWMCAC_ETL_SDELUP.fmw

Parameters:
- SourceDataset_ORACLE8I_DB = SDELUP   # Source Oracle Non-spatial Service
- DestDataset_GEODATABASE_SDE = sde   # Destination Esri ArcSDE Geodatabase Dataset

Readers:
- ORACLE8I_DB_1: ORACLE8I_DB from $(SourceDataset_ORACLE8I_DB) in EPSG:4259

Writers:
- GEODATABASE_SDE_1: GEODATABASE_SDE to $(DestDataset_GEODATABASE_SDE)

IWMCAC.WELL_BORE (reader ORACLE8I_DB_1)
    attributes: WELL_BORE_UWI varchar2(26), WELL_SURFACE_FLAG varchar2(1), TVDSS_M float, REF_ELEV_M float, DATA_SOURCE varchar2(5), LAT_PREF float, LON_PREF float, LAT_BH_PREF float, LON_BH_PREF float, PROJECT_NAME varchar2(20), INSTANCE_NAME varchar2(32), WELL_UWI varchar2(26), PARENT_WELL_BORE_UWI varchar2(26), SBU varchar2(30), SBU_CODE varchar2(10), DATA_QUALITY varchar2(12), WELL_BORE_NAME varchar2(40), WELL_BORE_NO varchar2(10), FULL_WELL_BORE_NAME varchar2(80), MAP_LABEL varchar2(20), IRIS21_UWI number(12,0), CHEVNO varchar2(26), COUNTRY varchar2(25), COUNTRY_CODE varchar2(2), INIT_CLASS varchar2(40), CURRENT_STATUS varchar2(40), BOREHOLE_TYPE varchar2(10), TD float, TD_UNIT varchar2(12), TD_M float,
      TVD_M float, REF_ELEV_TYPE varchar2(2), REF_ELEV float, REF_ELEV_UNIT varchar2(12), GR_WD_ELEV float, GR_WD_ELEV_UNIT varchar2(12), GR_WD_ELEV_M float, SPUD_DATE date, DRILLING_END_DATE date, FIELD_NAME varchar2(60), BASIN_NAME varchar2(60), CONCESSION varchar2(40), CONCESSION_CODE varchar2(10), OPERATOR varchar2(40), RIG_NAME varchar2(24), PLATFORM_NAME varchar2(24), PLATFORM_SLOT_NUMBER varchar2(12), ON_OFF_SHORE varchar2(3), DEPTH_UNITS varchar2(12), LAT_Y_ORIG float, LON_X_ORIG float, CRS_LAT_LON_XY_ORIG varchar2(40), CRS_LAT_LON_XY_ORIG_DATUM varchar2(40), CRS_LAT_LON_XY_ORIG_TYPE varchar2(40), LAT_ORIG float, LON_ORIG float, LAT_WGS84 float, LON_WGS84 float, X_PREF float, Y_PREF float,
      CRS_PREF_PROJECTION varchar2(40), LAT_Y_BH_ORIG float, LON_X_BH_ORIG float, CRS_LAT_LON_XY_BH_ORIG varchar2(40), CRS_LAT_LON_XY_BH_ORIG_DATUM varchar2(40), CRS_LAT_LON_XY_BH_ORIG_TYPE varchar2(40), LAT_BH_ORIG float, LON_BH_ORIG float, LAT_BH_WGS84 float, LON_BH_WGS84 float, X_BH_PREF float, Y_BH_PREF float, COMMENTS varchar2(240), CREATE_DATE date, CREATE_USER varchar2(32), UPDATE_DATE date, UPDATE_USER varchar2(32), SYNC_DATE date, SYNC_DATE_IWM date, ASSET_NAME varchar2(40), DATA_COMPLETENESS number(38,0), WELL_SURFACE_NAME varchar2(40), CRS_PREF_DATUM varchar2(40)
    -> NullReplace_REF_ELEV_M
NullReplace_REF_ELEV_M: NullAttributeReplacer
    SRC_ATTRS = REF_ELEV_M
    NEW_VALUE = 0
    -> MergeHeader [input 2]
    -> NullReplace_LON_BH
    -> FilterWellSurfaceFlag
NullReplace_LON_BH: NullAttributeReplacer
    SRC_ATTRS = LON_BH_PREF
    NEW_VALUE = @Value(LON_PREF)
    -> NullReplace_LAT_BH
NullReplace_LAT_BH: NullAttributeReplacer
    SRC_ATTRS = LAT_BH_PREF
    NEW_VALUE = @Value(LAT_PREF)
    -> CreateBottomholePt
CreateBottomholePt: 3DPointReplacer
    XVALATTR = @Value(LON_BH_PREF)
    YVALATTR = @Value(LAT_BH_PREF)
    ZVALATTR = @Value(TVDSS_M)
    POINT -> NullReplace_LAT_BH_OUTPUT [off]
    POINT -> IWMCAC.CIEP_WELLBORE_GEOM_SA (writer GEODATABASE_SDE_1)
NullReplace_LAT_BH_OUTPUT: Inspector [off]
IWMCAC.CIEP_WELLBORE_GEOM_SA (writer GEODATABASE_SDE_1)
    attributes: geodb_oid integer, OBJECTID integer, WELL_BORE_UWI char(26), PROJECT_NAME char(20), INSTANCE_NAME char(32), WELL_UWI char(26), PARENT_WELL_BORE_UWI char(26), WELL_SURFACE_FLAG char(1), SBU char(30), SBU_CODE char(10), DATA_QUALITY char(12), WELL_BORE_NAME char(40), WELL_BORE_NO char(10), FULL_WELL_BORE_NAME char(80), MAP_LABEL char(20), IRIS21_UWI double, CHEVNO char(26), COUNTRY char(25), COUNTRY_CODE char(2), INIT_CLASS char(40), CURRENT_STATUS char(40), BOREHOLE_TYPE char(10), TD double, TD_UNIT char(12), TD_M double, TVD_M double, TVDSS_M double, REF_ELEV_TYPE char(2), REF_ELEV double, REF_ELEV_UNIT char(12),
      REF_ELEV_M double, GR_WD_ELEV double, GR_WD_ELEV_UNIT char(12), GR_WD_ELEV_M double, SPUD_DATE date, DRILLING_END_DATE date, FIELD_NAME char(60), BASIN_NAME char(60), CONCESSION char(40), CONCESSION_CODE char(10), OPERATOR char(40), RIG_NAME char(24), PLATFORM_NAME char(24), PLATFORM_SLOT_NUMBER char(12), ON_OFF_SHORE char(3), DEPTH_UNITS char(12), DATA_SOURCE char(5), LAT_Y_ORIG double, LON_X_ORIG double, CRS_LAT_LON_XY_ORIG char(40), CRS_LAT_LON_XY_ORIG_DATUM char(40), CRS_LAT_LON_XY_ORIG_TYPE char(40), LAT_ORIG double, LON_ORIG double, LAT_PREF double, LON_PREF double, X_PREF double, Y_PREF double, CRS_PREF_PROJECTION char(40), LAT_Y_BH_ORIG double,
      LON_X_BH_ORIG double, CRS_LAT_LON_XY_BH_ORIG char(40), CRS_LAT_LON_XY_BH_ORIG_DATUM char(40), CRS_LAT_LON_XY_BH_ORIG_TYPE char(40), LAT_BH_ORIG double, LON_BH_ORIG double, LAT_BH_PREF double, LON_BH_PREF double, X_BH_PREF double, Y_BH_PREF double, COMMENTS char(240), CREATE_DATE date, CREATE_USER char(32), UPDATE_DATE date, UPDATE_USER char(32), SYNC_DATE date, SYNC_DATE_IWM date, ASSET_NAME char(40), DATA_COMPLETENESS integer, WELL_SURFACE_NAME char(40)
FilterWellSurfaceFlag: AttributeFilter
    ATTR_VALUES = W,<BLANK>,<UNFILTERED>
    ATTR_NAME = WELL_SURFACE_FLAG
    W -> CreateSurfacePt
CreateSurfacePt: 3DPointReplacer
    XVALATTR = @Value(LON_PREF)
    YVALATTR = @Value(LAT_PREF)
    ZVALATTR = @Value(REF_ELEV_M)
    POINT -> FilterWellSurfaceFlag_W [off]
    POINT -> IWMCAC.CIEP_WELLSURF_GEOM (writer GEODATABASE_SDE_1)
FilterWellSurfaceFlag_W: Inspector [off]
IWMCAC.CIEP_WELLSURF_GEOM (writer GEODATABASE_SDE_1)
    attributes: geodb_oid integer, OBJECTID integer, WELL_UWI char(26), SBU char(30), COUNTRY char(25), CONCESSION char(40), WELL_NAME char(160), MAP_LABEL char(20), SPUD_DATE date, OPERATOR char(40), FIELD_NAME char(60), PLATFORM_NAME char(24), PLATFORM_SLOT_NUMBER char(12), LAT_Y_ORIG double, LON_X_ORIG double, CRS_LAT_LON_XY_ORIG char(40), CRS_LAT_LON_XY_ORIG_DATUM char(40), CRS_LAT_LON_XY_ORIG_TYPE char(40), LAT_ORIG double, LON_ORIG double, LAT_PREF double, LON_PREF double, DATA_SOURCE char(5), COMMENTS char(240), CREATE_DATE date, CREATE_USER char(32), UPDATE_DATE date, UPDATE_USER char(32), SBU_CODE char(10), COUNTRY_CODE char(2),
      CONCESSION_CODE char(10), ASSET_NAME char(40), SYNC_DATE date, SYNC_DATE_IWM date
IWMCAC.WELL_BORE_PATH_PT (reader ORACLE8I_DB_1)
    attributes: WELL_BORE_UWI varchar2(26), SURVEY_NAME varchar2(25), MD float, TVD float, TVDSS float, LAT_OFFSET_WGS84 float, LON_OFFSET_WGS84 float, X_OFFSET_PREF float, Y_OFFSET_PREF float, SBU_CODE varchar2(10), COUNTRY_CODE varchar2(2), CONCESSION_CODE varchar2(10), INCLINATION float, AZIMUTH float, LAT_OFFSET_PREF float, LON_OFFSET_PREF float
    -> Sorter
Sorter
    SORT_PARM = WELL_BORE_UWI ALPHA ASCENDING SURVEY_NAME ALPHA ASCENDING MD NUMERIC ASCENDING
    SORTED -> MergePathPts [input 1]
IWMCAC.WELL_BORE_PATH_HDR (reader ORACLE8I_DB_1)
    attributes: WELL_BORE_UWI varchar2(26), SURVEY_NAME varchar2(25), DATA_SOURCE varchar2(5), CALC_METHOD varchar2(20), BH_LAT_OFFSET_WGS84 float, BH_LON_OFFSET_WGS84 float, BH_X_OFFSET_PREF float, BH_Y_OFFSET_PREF float, BH_MD float, BH_TVD float, BH_TVDSS float, TOTAL_SAMPLES number(38,0), DEPTH_UNITS varchar2(12), SBU_CODE varchar2(10), COUNTRY_CODE varchar2(2), CONCESSION_CODE varchar2(10), SYNC_DATE date, SYNC_DATE_IWM date, NORTH_REFERENCE varchar2(12), CONVERGENCE_ANGLE float, BH_LAT_OFFSET_PREF float, BH_LON_OFFSET_PREF float
    -> MergeHeader [input 1]
MergeHeader: FeatureMerger
    IGNORE_NULLS = Yes
    JOIN_KEYS = @Value(WELL_BORE_UWI) @Value(WELL_BORE_UWI)
    SUPPLIER_PREFIX_DUMMY = YES
    SUPPLIERS_FIRST = No
    PROCESS_DUPS = No
    MERGE_TYPE = Attributes Only
    MERGED -> MergePathPts [input 2]
MergePathPts: FeatureMerger
    IGNORE_NULLS = Yes
    JOIN_KEYS = @Value(WELL_BORE_UWI) @Value(WELL_BORE_UWI) @Value(SURVEY_NAME) @Value(SURVEY_NAME)
    SUPPLIER_PREFIX_DUMMY = YES
    SUPPLIERS_FIRST = No
    PROCESS_DUPS = No
    MERGE_TYPE = Attributes Only
    MERGED -> CalcPointLat
CalcPointLat: ExpressionEvaluator
    VAL_ATTR = POINT_LAT
    EXPRESSION = @Value(LAT_PREF)+@Value(LAT_OFFSET_PREF)
    -> CalcPointLon
CalcPointLon: ExpressionEvaluator
    VAL_ATTR = POINT_LON
    EXPRESSION = @Value(LON_PREF)+@Value(LON_OFFSET_PREF)
    -> IsFeetUnit
IsFeetUnit: Tester
    TEST_MODE = Automatic
    TEST_DESCRIPTION = ""
    TEST_CLAUSE:
      TEST @Value(DEPTH_UNITS) = FT
      TEST @Value(DEPTH_UNITS) = ft
    BOOL_OP = OR
    PASSED -> TVDSSToMeters
    FAILED -> CreateWellPathPt
TVDSSToMeters: ExpressionEvaluator
    VAL_ATTR = TVDSS
    EXPRESSION = @Value(TVDSS)*12.0/39.37
    -> MDToMeters
MDToMeters: ExpressionEvaluator
    VAL_ATTR = MD
    EXPRESSION = @Value(MD)*12.0/39.37
    -> CreateWellPathPt
CreateWellPathPt: 3DPointReplacer
    XVALATTR = @Value(POINT_LON)
    YVALATTR = @Value(POINT_LAT)
    ZVALATTR = @Value(TVDSS)
    POINT -> MeasureSetter
MeasureSetter
    GEOM_TYPE = Point
    MEASURE_VAL = @Value(MD)
    -> PointConnector
PointConnector
    BREAKATTR = WELL_BORE_UWI SURVEY_NAME
    LINE -> PointConnector_LINE [off]
    LINE -> IWMCAC.CIEP_WELLPATH_GEOM_SA (writer GEODATABASE_SDE_1)
IWMCAC.CIEP_WELLPATH_GEOM_SA (writer GEODATABASE_SDE_1)
    attributes: geodb_oid integer, OBJECTID integer, WELL_BORE_UWI char(26), SURVEY_NAME char(25), DATA_SOURCE char(5), CALC_METHOD char(20), FIELD_NAME char(60), BH_LAT_OFFSET_PREF double, BH_LON_OFFSET_PREF double, BH_X_OFFSET_PREF double, BH_Y_OFFSET_PREF double, BH_MD double, BH_TVD double, BH_TVDSS double, TOTAL_SAMPLES integer, DEPTH_UNITS char(12), SBU_CODE char(10), COUNTRY_CODE char(2), CONCESSION_CODE char(10), SYNC_DATE date, SYNC_DATE_IWM date, NORTH_REFERENCE char(12), CONVERGENCE_ANGLE double, SHAPE_LEN double
PointConnector_LINE: Inspector [off]
